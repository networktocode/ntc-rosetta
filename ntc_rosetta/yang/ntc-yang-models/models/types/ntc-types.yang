module ntc-types {
    yang-version "1";

    namespace "https://networktocode.com/yang/types";

    prefix "ntc-types";

    organization "Network To Code LLC.";

    contact "www.networktocode.com";

    description
        "Common types";

    revision "2019-05-02" {
        description
            "initial version";
        reference "0.0.1";
    }

    typedef ip-address {
        type union {
            type ipv4-address;
            type ipv6-address;
        }
        description
            "A bare IPv4 or IPv6 address.";
    }

    typedef ipv4-address {
        type string {
            pattern '(([0-9]|[1-9][0-9]|1[0-9][0-9]|2[0-4][0-9]|'        +
                    '25[0-5])\.){3}([0-9]|[1-9][0-9]|1[0-9][0-9]|2[0-4]'  +
                    '[0-9]|25[0-5])';
        }
        description
            "An IPv4 address in dotted quad notation using the default
            zone (copied from openconfig)";
    }

    typedef ipv6-address {
        type string {
            pattern
                // Must support compression through different lengths
                // therefore this regexp is complex.
                '(([0-9a-fA-F]{1,4}:){7}[0-9a-fA-F]{1,4}|'         +
                '([0-9a-fA-F]{1,4}:){1,7}:|'                        +
                '([0-9a-fA-F]{1,4}:){1,6}:[0-9a-fA-F]{1,4}|'        +
                '([0-9a-fA-F]{1,4}:){1,5}(:[0-9a-fA-F]{1,4}){1,2}|' +
                '([0-9a-fA-F]{1,4}:){1,4}(:[0-9a-fA-F]{1,4}){1,3}|' +
                '([0-9a-fA-F]{1,4}:){1,3}(:[0-9a-fA-F]{1,4}){1,4}|' +
                '([0-9a-fA-F]{1,4}:){1,2}(:[0-9a-fA-F]{1,4}){1,5}|' +
                '[0-9a-fA-F]{1,4}:((:[0-9a-fA-F]{1,4}){1,6})|'      +
                ':((:[0-9a-fA-F]{1,4}){1,7}|:)'                     +
                ')';
        }
        description
          "An IPv6 address represented as either a full address; shortened
          or mixed-shortened formats, using the default zone (copied from openconfig)";
    }
}
